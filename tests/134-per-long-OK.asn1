-- OK: Everything is fine
-- Also see .127 for narrower integer types.

-- iso.org.dod.internet.private.enterprise (1.3.6.1.4.1)
-- .spelio.software.asn1c.test (9363.1.5.1)
-- .134

ModulePERLong
	{ iso org(3) dod(6) internet (1) private(4) enterprise(1)
		spelio(9363) software(1) asn1c(5) test(1) 134 }
	DEFINITIONS AUTOMATIC TAGS ::=
BEGIN

    -- Supported only on 64-bit platforms.
	T ::= SEQUENCE {
		unsigned33  INTEGER (0..5000000000),    -- range 33 bits
		unsigned42  INTEGER (0..3153600000000), -- range 42 bits
		unsigned64  INTEGER (0..9223372036854775807), --range 64 bits TODO: Fails with anything bigger then 63bits
		signed33    INTEGER (-4000000000..4000000000), -- 33 bits
		signed33ext INTEGER (-4000000000..4000000000,...),
		signed64    INTEGER (-9223372036854775807..9223372036854775806) -- 64bits (1 less then max)
	}

END
